submodule dummy-submodule {
    yang-version 1.1;
    belongs-to dummy-belongs-to {
        prefix dummy-prefix; 
    }
    
    import dummy-import-1 {
        prefix "import-1";
    }
    import dummy-import-2 {
        prefix "import-2";
    }
}
