submodule dummy-submodule {
    yang-version 1.1;
    belongs-to dummy-belongs-to {
        prefix dummy-prefix; 
    }
    
    extension dummy-extension;
    feature dummy-feature;
    identity dummy-identity;
    typedef dummy-typedef {
        type string;
    }
    grouping dummy-grouping;
    leaf dummy-datadef {
        type uint32;
    }
    augment "dummy-augment"{}
    rpc dummy-rpc;
    notification dummy-notification;
    feature dummy-deviation;
}
