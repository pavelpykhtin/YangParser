module dummy-module {
    yang-version 1.1;
    namespace "urn:example:rock";
    prefix "example";
    
    organization "dummy-organization";
    contact "dummy-contact";
    description "dummy-description";
    reference "dummy-reference";
}
